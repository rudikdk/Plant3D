;; ValveCodeSelector.lsp
;; AutoLISP program for AutoCAD Plant 3D 2024
;; Allows user to select a value from a SQLite database and attach it
;; as a Valve Code to a selected Plant 3D asset.

(defun c:VALVECODE ( / conn rs values dcl_id choice index code ent)
  (vl-load-com)
  (setq conn (vlax-create-object "ADODB.Connection"))
  (setq connstr "dsn=SQLite3 Datasource;database=C:\\Users\\RudiSchlesingerKærga\\Lundsby\\CAD Maintenance - CAD Maintenance\\Cad Maintenance\\Sync Folder\\Lundsby AutoCAD Plant 3D 2024 Content\\CPak DIN\\LB DIN Valves and Instruments.pcat")
  (vlax-invoke-method conn 'Open connstr)
  (setq rs (vlax-create-object "ADODB.Recordset"))
  (vlax-invoke-method rs 'Open "SELECT PartSizeLongDesc FROM EngineeringItems" conn)
  (setq values '())
  (while (= (vlax-get-property rs 'EOF) :vlax-false)
    (setq values (cons (vlax-get-property (vlax-invoke-method (vlax-get-property rs "Fields") "Item" "PartSizeLongDesc") "Value") values))
    (vlax-invoke-method rs 'MoveNext)
  )
  (setq values (reverse values))
  (vlax-invoke-method rs 'Close)
  (vlax-release-object rs)
  (vlax-invoke-method conn 'Close)
  (vlax-release-object conn)
  (setq dcl_id (load_dialog "ValveCodeSelector.dcl"))
  (if (new_dialog "valve_dialog" dcl_id)
    (progn
      (start_list "valveList")
      (foreach itm values (add_list itm))
      (end_list)
      (action_tile "accept" "(setq choice (get_tile \"valveList\"))(done_dialog 1)")
      (action_tile "cancel" "(done_dialog 0)")
      (if (= 1 (start_dialog))
        (progn
          (setq index (atoi choice))
          (setq code (nth index values))
          (unload_dialog dcl_id)
          (prompt "\nSelect Plant 3D asset: ")
          (setq ent (car (entsel)))
          (if ent
            (progn
              (if (not (tblsearch "APPID" "VALVECODE"))
                (entmake (list (cons 0 "APPID") (cons 2 "VALVECODE") (cons 70 0)))
              )
              (entmod (append (entget ent)
                              (list (list -3 (list (cons 1001 "VALVECODE") (cons 1000 code))))))
              (entupd ent)
              (princ (strcat "\nValve Code '" code "' attached."))
            )
            (prompt "\nNothing selected.")
          )
        )
        (progn (unload_dialog dcl_id) (prompt "\nOperation cancelled."))
      )
    )
    (prompt "\nCould not load dialog.")
  )
  (princ)
)

(princ "\nType VALVECODE to assign Valve Code.\n")
